Dim oDocs As Documents = ThisApplication.Documents
'Dim oDrawingDoc As DrawingDocument

Dim oTG As TransientGeometry
oTG = ThisApplication.TransientGeometry

Dim oTM As TransactionManager = ThisApplication.TransactionManager
Dim oT As Transaction

Dim items As Integer = 0

Dim sActiveDocName As String
Dim sActiveSheetName As String
sActiveDocName = ThisApplication.ActiveDocument.DisplayName
Dim dDoc As DrawingDocument = ThisApplication.ActiveDocument
sActiveSheetName = dDoc.ActiveSheet.Name
Dim curDate As String = Date.Now.ToShortDateString

For Each oDoc As Document In ThisApplication.Documents.VisibleDocuments
'	If oDoc.DisplayName = sActiveDocName Then
'		Continue For 
'	End If
	'msgbox("test")
    If oDoc.DocumentType = DocumentTypeEnum.kDrawingDocumentObject Then '12292 = drawing doc
		Dim oDrawingDoc As DrawingDocument
		oDrawingDoc = oDoc
		oDrawingDoc.Activate()
		'oDrawingDoc.ClientViews
		
		For Each sksym As SketchedSymbol In oDrawingDoc.ActiveSheet.SketchedSymbols
			If sksym.Name = "CHECK_PRINT_JR" Then
				sksym.Delete()
			End If
		Next
		
		ThisApplication.CommandManager.ControlDefinitions.Item("AppZoomallCmd").Execute()
		iLogicVb.UpdateWhenDone=True

		oDoc.Dirty = True
		oDoc.Save
				
		'Logger.Info("{0} SAVED",{oDoc.FullFileName})
		items += 1
	Else
		
    End If
Next

dDoc.Activate()

MsgBox("Saved " & items & " drawings")
