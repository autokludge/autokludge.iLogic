Dim oDocs As Documents = ThisApplication.Documents
Dim oDoc As Document
Dim oDrawingDoc As DrawingDocument
Dim sActiveDocName = ThisApplication.ActiveDocument.DisplayName

Dim oTG As TransientGeometry = ThisApplication.TransientGeometry

Dim oTM As TransactionManager = ThisApplication.TransactionManager
Dim oT As Transaction

Dim o_SourceSketchedSymbol As SketchedSymbol 
Dim o_SourceSketchedSymbolDef As SketchedSymbolDefinition
Dim listTextValues As New Dictionary(Of String,String)

Dim oSelectSet As SelectSet = ThisApplication.ActiveDocument.SelectSet
If oSelectSet.Count = 0 Then
	MsgBox("none selected")
	Return
End If

For Each selection In oSelectSet
    If TypeOf selection Is SketchedSymbol Then
	    o_SourceSketchedSymbol = DirectCast(selection, SketchedSymbol)
		o_SourceSketchedSymbolDef = o_SourceSketchedSymbol.Definition
		
		For Each oTB As Inventor.TextBox In o_SourceSketchedSymbolDef.Sketch.TextBoxes
			Dim sFieldKey As String
			Dim sFieldValue As String
			'Logger.Info(oTB.FormattedText)
			If Not oTB.FormattedText.Contains("<Prompt") Then
				continue for
			End If
			Try
				sFieldValue = o_SourceSketchedSymbol.GetResultText(oTB)
				sFieldKey = oTB.Text
				Logger.Info(sFieldKey & " ::: " & sFieldValue)			
				listTextValues.Add(sFieldKey,sFieldValue)
			Catch ex As Exception 
				Logger.Info("ERROR ::: " & ex.Message)
				Continue For
			End Try
		Next
		
		Exit For
    End If
Next

For Each oDoc In ThisApplication.Documents.VisibleDocuments
'	If oDoc.DisplayName = sActiveDocName Then
'		Continue For 
'	End If
	'msgbox("test")
    If oDoc.DocumentType = 12292 Then '12292 = drawing doc
		oDrawingDoc = DirectCast(oDoc,DrawingDocument)
		
		If oDrawingDoc.DisplayName = sActiveDocName And oDrawingDoc.Sheets.Count = 1 Then
			Continue For 
		End If
		
        oT = oTM.StartTransaction(oDoc, "Update Drawing Note")

		question = MessageBox.Show("Do you want to copy to " & oDoc.DisplayName & "?", "iLogic Question",MessageBoxButtons.YesNo,MessageBoxIcon.Question)

        'Set condition based On answer
        If Not question = vbYes Then
			Continue For
		End If
		
		Dim updated_SkSymDef = o_SourceSketchedSymbolDef.CopyTo(oDoc, True)
				
		For Each oSketchSymbol As SketchedSymbol In oDrawingDoc.ActiveSheet.SketchedSymbols
			
			Logger.Info("  In SketchedSymbol: " & oSketchSymbol.Name)
			
			For Each oTB As Inventor.TextBox In oSketchSymbol.Definition.Sketch.TextBoxes
				Dim sFieldText As String
				Dim sFieldKey As String
				If Not oTB.FormattedText.Contains("<Prompt") Then
					Continue For
				End If
				Try
					sFieldText = oSketchSymbol.GetResultText(oTB)
					sFieldKey = oTB.Text
					Dim updateVal = listTextValues(sFieldKey)
					oSketchSymbol.SetPromptResultText(oTB, updateVal)
				Catch ex As Exception 
					Logger.Error(ex.Message)
					Continue For
				End Try
								
			Next
		Next	
		
		oT.End()
		oDoc.Update()
		
		items += 1
	Else
		
    End If
Next

MsgBox("Copied symbol to " & items & " drawings")
