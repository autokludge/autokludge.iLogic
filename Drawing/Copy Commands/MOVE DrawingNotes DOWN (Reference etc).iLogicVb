Dim oDocs As Documents = ThisApplication.Documents
Dim oDoc As Document
Dim oDrawingDoc As DrawingDocument

Dim oTG As TransientGeometry
oTG = ThisApplication.TransientGeometry

Dim oTM As TransactionManager = ThisApplication.TransactionManager
Dim oT As Transaction

Dim items As Integer = 0

Dim oDNote As GeneralNote
Dim oSelectSet As SelectSet
oSelectSet = ThisApplication.ActiveDocument.SelectSet

Dim sActiveDocName As String
Dim sActiveSheetName As String
sActiveDocName = ThisApplication.ActiveDocument.DisplayName
Dim dDoc As DrawingDocument = ThisApplication.ActiveDocument
sActiveSheetName = dDoc.ActiveSheet.Name

Dim oNotesToMove As ObjectCollection
Dim oNotesToMoveStyle As ObjectCollection
Dim oNotesToMovePosition As ObjectCollection
Dim oNotesToMoveWS As ObjectCollection
Dim oNotesToMoveHJ As New ArrayList '0 index
Dim oNotesToMoveVJ As New ArrayList
Dim oNotesToMoveLS As New ArrayList
Dim oNotesToMoveLST As New ArrayList
oNotesToMove = ThisApplication.TransientObjects.CreateObjectCollection '1 index
oNotesToMoveStyle = ThisApplication.TransientObjects.CreateObjectCollection
oNotesToMovePosition = ThisApplication.TransientObjects.CreateObjectCollection
oNotesToMoveWS = ThisApplication.TransientObjects.CreateObjectCollection
'oNotesToMoveHJ = ThisApplication.TransientObjects.CreateObjectCollection
'oNotesToMoveVJ = ThisApplication.TransientObjects.CreateObjectCollection

If oSelectSet.Count = 0 Then
	MsgBox("none selected")
	return
End If

Dim oMoveStr As String
Dim oMove As Double
oMoveStr = InputBox("Enter Desired Position", "Position", "")
oMove = CDbl(oMoveStr)/10

oT = oTM.StartTransaction(ThisApplication.ActiveDocument, "Moved Drawing Note")

For Each selection In oSelectSet
    If TypeOf selection Is GeneralNote Then
	    oDNote = selection
	    Dim new_point As Point2d = ThisApplication.TransientGeometry.CreatePoint2d(oDNote.Position.X, oDNote.Position.Y - oMove )
		oDNote.Position = new_point
		oNotesToMove.Add(oDNote.FormattedText)
		'oNotesToMoveStyle.Add(oDNote.TextStyle)
		'oNotesToMovePosition.Add(oDNote.Position)
		'oNotesToMoveWS.Add(oDNote.WidthScale.ToString)
		'msgbox(oDNote.HorizontalJustification.ToString)
		'oNotesToMoveHJ.Add(oDNote.HorizontalJustification.ToString)
		'oNotesToMoveVJ.Add(oDNote.VerticalJustification.ToString)
		'oNotesToMoveLST.Add(oDNote.LineSpacingType)
		'oNotesToMoveLS.Add(oDNote.LineSpacing)		
    End If
Next

'msgbox("test")





oDoc = ThisApplication.ActiveDocument

oT.End()
oDoc.Update()

'MsgBox("Moved " & oNotesToMove.Count & " notes")
