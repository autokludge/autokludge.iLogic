If ThisDoc.Document.DocumentType <> DocumentTypeEnum.kDrawingDocumentObject Then
	MsgBox("Please run this from a drawing document")
	Return
End if

' Set a reference to the active drawing document
Dim oDoc As DrawingDocument
oDoc = ThisDoc.Document

' Set a reference to the active sheet
Dim oSheet As Sheet
oSheet = oDoc.ActiveSheet

Dim oSelectSet As SelectSet
oSelectSet = oDoc.SelectSet

Dim oDrawingDim As DrawingDimension
Dim selection As Object
' Iterate over all dimensions in the drawing and
' center them if they are linear or angular.
Dim count = 0
For Each selection In oSelectSet
    If TypeOf selection Is LinearGeneralDimension Or _
       TypeOf selection Is AngularGeneralDimension Then
	    oDrawingDim = selection
		oDrawingDim.Precision = 0
		oDrawingDim.Text.FormattedText = "<DimensionValue/> PL"
		count += 1
    End If
Next

If count < 1 Then
	MsgBox("Please select dimensions first")
End If
