' Set a reference to the active drawing document
Dim oDoc As DrawingDocument
oDoc = ThisDoc.Document

' Set a reference to the active sheet
Dim oSheet As Sheet
oSheet = oDoc.ActiveSheet

Dim oSelectSet As SelectSet
oSelectSet = oDoc.SelectSet

Dim oDrawingDim As DrawingDimension
Dim selection As Object
' Iterate over all dimensions in the drawing and
' center them if they are linear or angular.

For Each selection In oSelectSet
    If TypeOf selection Is LinearGeneralDimension Or _
       TypeOf selection Is AngularGeneralDimension Then
	    oDrawingDim = selection
		oDrawingDim.Precision = 0
        precision = oDrawingDim.Precision
		rounding = 2 * Pow(10, (0-precision-1))
		modelDim = oDrawingDim.ModelValue
		orideDim = (Round(modelDim / rounding)) * rounding * 10
		
		myparam = InputBox("NOM VALUE= ", "VALUE?", orideDim)
		Dim num_holes As Double
		num_holes = CDbl(myparam)/10
		
		oDrawingDim.OverrideModelValue = num_holes
		
		'oDrawingDim.Text.FormattedText="<DimensionValue/>"
    End If
Next
