' Set a reference to the active drawing document
Dim oDoc As DrawingDocument
oDoc = ThisDoc.Document

' Set a reference to the active sheet
Dim oSheet As Sheet
oSheet = oDoc.ActiveSheet

Dim oSelectSet As SelectSet
oSelectSet = oDoc.SelectSet

Dim oDrawView As DrawingView

Dim selection As Object
' Iterate over all dimensions in the drawing and
' center them if they are linear or angular.

For Each selection In oSelectSet
    If TypeOf selection Is DrawingView Then
	    oDrawView = selection
        
		Dim oOriginInd As OriginIndicator = oDrawView.OriginIndicator
		
		oOriginInd.Visible = False
    End If
Next
