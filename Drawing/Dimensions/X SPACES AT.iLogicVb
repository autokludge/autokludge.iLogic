' Set a reference to the active drawing document
Dim oDoc As DrawingDocument
oDoc = ThisDoc.Document

' Set a reference to the active sheet
Dim oSheet As Sheet
oSheet = oDoc.ActiveSheet

Dim oSelectSet As SelectSet
oSelectSet = oDoc.SelectSet

If oSelectSet.Count < 1 Then
	Dim hd = ThisApplication.CommandManager.Pick(SelectionFilterEnum.kDrawingDimensionFilter, "Pick a hole dimension")
	oDoc.SelectSet.Select(hd)
End If

Dim selection As Object
' Iterate over all dimensions in the drawing and
' center them if they are linear or angular.

'4 HOLES - <DimensionValue/><Br/><StyleOverride Bold='True' Italic='True'>TOP FLANGE ONLY</StyleOverride>

For Each selection In oSelectSet
    If TypeOf selection Is LinearGeneralDimension Then
	    Dim ddim As DrawingDimension = selection
		
		myparam = InputBox("Spacing = ?", "Spaces?", 100)
		Dim spacing_mm As Double = CDbl(myparam)
		
		Dim overall_cm As Double = ddim.ModelValue
		Dim pitches = (overall_cm * 10) / spacing_mm

		Dim spacing_text = String.Format("{0:N1}", {spacing_mm}).Replace(".0","")
		ddim.Text.FormattedText = String.Format("{0} SPACES @ {1} = <DimensionValue/>",{pitches, spacing_text})
    End If
Next
