If ThisDoc.Document.DocumentType <> DocumentTypeEnum.kDrawingDocumentObject Then
	Return
End If

Dim drg As DrawingDocument = ThisDoc.Document
Dim leadernotes As LeaderNotes = drg.ActiveSheet.DrawingNotes.LeaderNotes
Dim stocknumber_formattedtext = "<StyleOverride FontSize='0.5'><Property Document='model' PropertySet='Design Tracking Properties' Property='Stock Number' FormatID='{32853F0F-3444-11D1-9E93-0060B03C1CA6}' PropertyID='55'>STOCK NUMBER</Property></StyleOverride>"

Dim curve_segment As DrawingCurveSegment = ThisApplication.CommandManager.Pick(SelectionFilterEnum.kDrawingCurveSegmentFilter, "Select part to add Stock Number for.")
Dim curve As DrawingCurve = curve_segment.Parent
Logger.Info("create intent")
Dim attach As GeometryIntent = drg.ActiveSheet.CreateGeometryIntent(curve, 0.75)
Dim textpoint As Point2d = ThisApplication.TransientGeometry.CreatePoint2d(attach.PointOnSheet.X+0.5,attach.PointOnSheet.Y+1)
Dim leader_points As ObjectCollection = ThisApplication.TransientObjects.CreateObjectCollection()
leader_points.Add(textpoint)
leader_points.Add(attach)

Dim newnote As LeaderNote = leadernotes.Add(leader_points, stocknumber_formattedtext)
drg.Update()
