Dim oDocs As Documents = ThisApplication.Documents
Dim oDoc As Document
Dim oDrawingDoc As DrawingDocument

Dim oTG As TransientGeometry
oTG = ThisApplication.TransientGeometry

Dim oTM As TransactionManager = ThisApplication.TransactionManager
Dim oT As Transaction

Dim oSelectSet As SelectSet
oSelectSet = ThisApplication.ActiveDocument.SelectSet

Dim oldtext = ""
If oSelectSet.Count >= 1 Then
	Dim sel = oSelectSet.Item(1)
	If TypeOf sel Is DrawingNote Then
		Dim dn_sel As DrawingNote = sel
		oldtext = dn_sel.Text
	End If
End If

Dim sOldDrawingNum As String
Dim sNewDrawingNum As String
sOldDrawingNum = InputBox("Enter Old Text", "OLD TEXT", oldtext)
sNewDrawingNum = InputBox("Enter New Text", "NEW TEXT", "")

if sOldDrawingNum = "" Then
	msgbox("Command Cancelled")
	return
end if

Dim items As Integer = 0

For Each oDoc In ThisApplication.Documents.VisibleDocuments
    If oDoc.DocumentType = 12292 Then '12292 = drawing doc
		oDrawingDoc = oDoc
        oT = oTM.StartTransaction(oDoc, "Update Drawing Note")

		For Each oSheet As Sheet In oDrawingDoc.Sheets
			
			For Each oDrawingNote As DrawingNote In oSheet.DrawingNotes
				
				If oDrawingNote.Text.Contains(sOldDrawingNum) Then
					
					items += 1
					
					'oDrawingNote.HorizontalJustification = HorizontalTextAlignmentEnum.kAlignTextCenter
					'oDrawingNote.VerticalJustification = VerticalTextAlignmentEnum.kAlignTextMiddle
					
					oDrawingNote.FormattedText = oDrawingNote.FormattedText.Replace(sOldDrawingNum, sNewDrawingNum)
					'oDrawingNote.WidthScale = 0.9
					'oDrawingNote.Position = oTG.CreatePoint2d(oDrawingNote.Position.X+0.1,oDrawingNote.Position.Y)
					
				End If
				
			Next
			Logger.Info("{0}:: {1}:: {2} items replaced",{oDrawingDoc.DisplayName,oSheet.Name,items})
			
		Next
		
		oT.End()
		oDoc.Update()
		
		
	Else
		
    End If
Next

MsgBox("Changed " & items & " places")
