Dim oDocs As Documents = ThisApplication.Documents
Dim oDoc As Document
Dim oDrawingDoc As DrawingDocument

Dim oTG As TransientGeometry
oTG = ThisApplication.TransientGeometry

Dim oTM As TransactionManager = ThisApplication.TransactionManager
Dim oT As Transaction

Dim stampName as string = "Copy of prelimchkincom"

Dim items As Integer = 0

Dim sTags() As String = New System.String() {}
Dim sValues() As String = New System.String() {}

Dim sOldDrawingNum As String
Dim sOldDrawingNum2 As String
Dim sOldDrawingNum3 As String
Dim sNewDrawingNum As String
Dim sNewDrawingNum2 As String
Dim sNewDrawingNum3 As String

sOldDrawingNum = "EN10216-2, WB36 / 15NiCuMoNb5, 141.3 OD x 12.1 THICK PIPE"
sOldDrawingNum2 = "EN10216-2, WB36 / 15NiCuMoNb5, 141.3 OD x 12.1 THICK 90deg ELBOW"
sOldDrawingNum3 = "EN10216-2, WB36 / 15NiCuMoNb5, 141.3 OD x 12.1 THICK 45deg ELBOW"
sNewDrawingNum = "DN125 SEAMLESS CARBON STEEL (PBE), SCH XXS PIPE, ASME B36.10M, ASTM A106 Gr B"
sNewDrawingNum2 = "DN125 90deg, 3D RADIUS, BW, SCH XXS ELBOW, ASME B16.9, ASTM A234 GR WPB"
sNewDrawingNum3 = "DN125 45deg, 3D RADIUS, BW, SCH XXS ELBOW, ASME B16.9, ASTM A234 GR WPB"

Dim sCellVal As String

For Each oDoc In ThisApplication.Documents.VisibleDocuments
    If oDoc.DocumentType = 12292 Then '12292 = drawing doc
		oDrawingDoc = oDoc
        oT = oTM.StartTransaction(oDoc, "Replace Text Partslist-CS")

		For Each oSheet As Sheet In oDrawingDoc.Sheets
			
			If oSheet.PartsLists.Count = 0 Then
				Continue For
			End If
			
			Dim sRepStr As String
			
			' Set a reference to the first parts list on the active sheet.
		    ' This assumes that a parts list is on the active sheet.
		    Dim oPartList As PartsList
		    oPartList = oSheet.PartsLists.Item(1)

			For Each oRow As PartsListRow In oPartList.PartsListRows
				
				For Each oCell As PartsListCell In oRow
					
					sCellVal = oCell.Value
					
					If Not oCell.Static And (sCellVal.Contains(sOldDrawingNum) Or sCellVal.Contains(sOldDrawingNum2) Or sCellVal.Contains(sOldDrawingNum3)) Then
						'MsgBox("Item found - not static")
					End If
					
					If sCellVal.Contains(sOldDrawingNum) Then
						
						oCell.Value = sCellVal.Replace(sOldDrawingNum, sNewDrawingNum)
						items += 1
						
					End If
					
					If sCellVal.Contains(sOldDrawingNum2) Then
						
						oCell.Value = sCellVal.Replace(sOldDrawingNum2, sNewDrawingNum2)
						items += 1
						
					End If
					
					If sCellVal.Contains(sOldDrawingNum3) Then
						
						oCell.Value = sCellVal.Replace(sOldDrawingNum3, sNewDrawingNum3)
						items += 1
						
					End If
					
				Next
				
			Next				
			
		Next
		
		oT.End()
		oDoc.Update()
		
	Else
		
    End If
Next

MsgBox("Changed " & items & " places")
