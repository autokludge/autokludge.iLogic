Imports System.Collections
Sub Main()

If ThisDoc.Document.DocumentType <> DocumentTypeEnum.kDrawingDocumentObject Then
	MsgBox("Run from drawing document")
	Return
End If

Dim aDoc As DrawingDocument = ThisDoc.Document
Dim aSheet As Sheet = aDoc.ActiveSheet

If aSheet.PartsLists.Count < 1 Then
	MsgBox("Parts list required")
	Return
End If

Dim aPartsList As PartsList = aSheet.PartsLists(1)

Try
	Dim itemCol = aPartsList.PartsListColumns.Item("Item")
Catch
	MsgBox("item column not found")
	Return
End Try

Dim anComparator = New AlphanumComparator()
Dim plr As PartsListRows = aPartsList.PartsListRows

Dim i = 1
While i < plr.Count()
	Dim j = i
	Logger.Info("Compare: {0}, {1} = {2}",plr(j).Item("Item").Value, plr(j+1).Item("Item").Value,anComparator.Compare(plr(j).Item("Item").Value, plr(j+1).Item("Item").Value))
	While j > 0 And anComparator.Compare(plr(j).Item("Item").Value, plr(j+1).Item("Item").Value) > 0
		Try
			plr(j+1).Reposition(j, True)
		Catch
			Logger.Error("didn't reposition")
		End Try	
		j = j-1
	End While
	i = i+1
End While


	
End Sub


''' <summary>
''' Sorts alphanumerically.
''' </summary>
Public Class AlphanumComparator
    Implements IComparer

    Public Function Compare(ByVal x As Object,
                            ByVal y As Object) As Integer Implements IComparer.Compare

        ' [1] Validate the arguments.
        Dim s1 As String = x
        If s1 = Nothing Then
            Return 0
        End If

        Dim s2 As String = y
        If s2 = Nothing Then
            Return 0
        End If

        Dim len1 As Integer = s1.Length
        Dim len2 As Integer = s2.Length
        Dim marker1 As Integer = 0
        Dim marker2 As Integer = 0

        ' [2] Loop over both Strings.
        While marker1 < len1 And marker2 < len2

            ' [3] Get Chars.
            Dim ch1 As Char = s1(marker1)
            Dim ch2 As Char = s2(marker2)

            Dim space1(len1) As Char
            Dim loc1 As Integer = 0
            Dim space2(len2) As Char
            Dim loc2 As Integer = 0

            ' [4] Collect digits for String one.
            Do
                space1(loc1) = ch1
                loc1 += 1
                marker1 += 1

                If marker1 < len1 Then
                    ch1 = s1(marker1)
                Else
                    Exit Do
                End If
            Loop While Char.IsDigit(ch1) = Char.IsDigit(space1(0))

            ' [5] Collect digits for String two.
            Do
                space2(loc2) = ch2
                loc2 += 1
                marker2 += 1

                If marker2 < len2 Then
                    ch2 = s2(marker2)
                Else
                    Exit Do
                End If
            Loop While Char.IsDigit(ch2) = Char.IsDigit(space2(0))

            ' [6] Convert to Strings.
            Dim str1 = New String(space1)
            Dim str2 = New String(space2)

            ' [7] Parse Strings into Integers.
            Dim result As Integer
            If Char.IsDigit(space1(0)) And Char.IsDigit(space2(0)) Then
                Dim thisNumericChunk = Integer.Parse(str1)
                Dim thatNumericChunk = Integer.Parse(str2)
                result = thisNumericChunk.CompareTo(thatNumericChunk)
            Else
                result = str1.CompareTo(str2)
            End If

            ' [8] Return result if not equal.
            If Not result = 0 Then
                Return result
            End If
        End While

        ' [9] Compare lengths.
        Return len1 - len2
    End Function
End Class
