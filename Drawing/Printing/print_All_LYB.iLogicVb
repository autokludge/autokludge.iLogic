'HKEY_CURRENT_USER\Software\Acro Software Inc\CPW
'Filename -- full file path
'Title -- filename

Dim myWS As Object
Dim i_RegKey As String = "HKEY_CURRENT_USER\Software\Acro Software Inc\CPW\Title"

Dim regVal As String

Try
	myWS = CreateObject("WScript.Shell")
	regVal = myWS.RegRead(i_RegKey)
Catch
End Try


Dim oDocs As Documents = ThisApplication.Documents
Dim oDoc As Document
Dim oDrawingDoc As DrawingDocument

Dim oTG As TransientGeometry
oTG = ThisApplication.TransientGeometry

Dim oTM As TransactionManager = ThisApplication.TransactionManager
Dim oT As Transaction

Dim items As Integer = 0

Dim sTags() As String = New System.String() {}
Dim sValues() As String = New System.String() {}

For Each oDoc In ThisApplication.Documents.VisibleDocuments
    If oDoc.DocumentType = 12292 Then '12292 = drawing doc
		oDrawingDoc = oDoc
        oT = oTM.StartTransaction(oDoc, "Update Sheet Revision")

		For Each oSheet As Sheet In oDrawingDoc.Sheets
			
			For Each oAutoCADBlock As AutoCADBlock In oSheet.AutoCADBlocks
				
				If Not oAutoCADBlock.Name.Contains("LYB-INVENTOR-SHT")
					Continue For
				End If
				
				'hope this works
				Try
					oAutoCADBlock.GetPromptTextValues(sTags, sValues)
					
					'Dim s As String = sTags.ToString
					'msgbox(s)
					
					Dim i As Integer

        			Dim iCount As Integer

        			iCount = UBound(sTags)

        			'Debug.Print("icount = " & iCount)

        			' display attribute tag and value
					'sTags(1) = "DRAWINGNUMBER"
					'sValues(1) = "0"
					
					Dim sKKS As String
					Dim revNum As String = ""
		
        			For i = 0 To iCount

						If sTags(i) = "DRAWINGNUMBER" Then
							sKKS = sValues(i)
							Exit For 							
						End If
						If sTags(i) = "REVISION" Then
							revNum = sValues(i)
						End If
						
						i = i + 1
						
        			Next
					
					Dim sVal As String = sKKS.Replace("/","_") & ".PDF"
					'myWS.RegWrite(i_RegKey, sVal, "REG_SZ")
					
					Dim DPM As DrawingPrintManager = oDrawingDoc.PrintManager
					
					'myWS.RegWrite(i_RegKey, sVal, "REG_SZ")
					DPM.Printer = "CutePDF Writer"
					DPM.PrintRange = PrintRangeEnum.kPrintCurrentSheet
					DPM.SubmitPrint()
					
					myWS.RegWrite(i_RegKey, sVal, "REG_SZ")
					
					System.Threading.Thread.CurrentThread.Sleep(7000)
					
					items += 1
				Catch
					MsgBox("failure")
				End Try
			Next
			
		Next
		
		oT.End()
		oDoc.Update()
		
	Else
		
    End If
Next

MsgBox("Printed " & items & " drawings")
