If ThisDoc.Document.DocumentType <> DocumentTypeEnum.kDrawingDocumentObject Then
	MsgBox("Run on a drawing")
	Return
End If

Dim r = 251
Dim g = 247
Dim b = 238

Dim c As Color = ThisApplication.TransientObjects.CreateColor(r,g,b)

Dim d As DrawingDocument = ThisDoc.Document
d.SheetSettings.SheetColor = c
d.Update()
