If ThisDoc.Document.DocumentType <> DocumentTypeEnum.kDrawingDocumentObject Then
	MsgBox("Run on a drawing")
	Return
End If

Dim r = 255
Dim g = 255
Dim b = 255

Dim c As Color = ThisApplication.TransientObjects.CreateColor(r,g,b)

Dim d As DrawingDocument = ThisDoc.Document
d.SheetSettings.SheetColor = c
d.Update()
