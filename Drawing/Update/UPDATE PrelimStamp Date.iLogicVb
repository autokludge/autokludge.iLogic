Dim oDocs As Documents = ThisApplication.Documents
Dim oDoc As Document
Dim oDrawingDoc As DrawingDocument

Dim oTG As TransientGeometry
oTG = ThisApplication.TransientGeometry

Dim oTM As TransactionManager = ThisApplication.TransactionManager
Dim oT As Transaction

Dim stampName as string = "Copy of prelimchkincom"

Dim items As Integer = 0

For Each oDoc In ThisApplication.Documents.VisibleDocuments
    If oDoc.DocumentType = 12292 Then '12292 = drawing doc
		oDrawingDoc = oDoc
        oT = oTM.StartTransaction(oDoc, "Remove Prelim Stamp")

		For Each oSheet As Sheet In oDrawingDoc.Sheets
			
			For Each oAutoCADBlock As AutoCADBlock In oSheet.AutoCADBlocks
				
				If oAutoCADBlock.Name.Contains(stampName) Then
					
					items += 1
					
					oAutoCADBlock.Delete()
					
				End If
				
			Next
			
			For Each oSkSymbol As SketchedSymbol In oSheet.SketchedSymbols
				If oSkSymbol.Name.Contains("PRELIM") Then
					items += 1
					
					oSkSymbol.Delete
				End If
			Next
			
		Next
		
		oT.End()
		oDoc.Update()
		
	Else
		
    End If
Next

MsgBox("Changed " & items & " places")
